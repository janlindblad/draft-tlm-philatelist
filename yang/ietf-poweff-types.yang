module ietf-poweff-types {
  yang-version 1.1;
  namespace "urn:ietf:params:xml:ns:yang:ietf-poweff-types";
  prefix ietf-poweff-types;

  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
     Editor:  Marisol Palmero
              <mailto:mpalmero@cisco.com>";
  description
    "This YANG module defines basic quantities, measurement units
    and sensor types for the POWEFF framework.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions  
  
     Relating to IETF Documents
     (https://trustee.ietf.org/license-info).

     This version of this YANG module is part of RFC XXXX
     (https://www.rfc-editor.org/info/rfcXXXX); see the RFC itself
     for full legal notices.";
  
  revision 2023-10-12 {
    description
      "Initial revision of POWEFF types";
    reference
      "RFC XXXX: ...";
  }

  typedef something { // FIXME: Used when we haven't decided the type yet
    type string;
  }
  typedef xpath {
    type string; // FIXME: Proper type needed
  }
  typedef sample-frequency {
    type string; // FIXME: Proper type needed
  }

  // ========== SENSOR-CLASS ==============================
  identity sensor-class {
    description "Sensor's relation to the asset it sits on.";
  }
  identity sc-input {
    base sensor-class;
    description "Sensor reports input quantity of the asset it sits 
      on.";
  }
  identity sc-output {
    base sensor-class;
    description "Sensor reports output quantity of the asset it sits 
      on.";
  }
  identity sc-allocated {
    base sensor-class;
    description "Sensor reports (maximum) allocated quantity of the 
      asset it sits on.";
  }

  // ========== SENSOR-QUANTITY ==============================
  identity sensor-quantity {
    description "Sensor's quantity being measured.";
  }
  identity sq-voltage {
    base sensor-quantity;
    description "Sensor reports electric tension, voltage.";
  }
  identity sq-current {
    base sensor-quantity;
    description "Sensor reports electric current.";
  }
  identity sq-power {
    base sensor-quantity;
    description "Sensor reports power draw (energy per unit of time).";
  }
  identity sq-power-apparent {
    base sq-power;
    description "Sensor reports apparent power, i.e. average electrical
      current times voltage (in VA).";
  }
  identity sq-power-true {
    base sq-power;
    description "Sensor reports true power, i.e. integral over current
      and voltage at each instant in time.";
  }
  identity sq-energy {
    base sensor-quantity;
    description "Sensor reports actual energy drawn by asset.";
  }
  identity sq-co2-emission {
    base sensor-quantity;
    description "Sensor reports CO2 (carbon dioxide) emission by 
      asset.";
  }
  identity sq-co2eq-emission {
    base sensor-quantity;
    description "Sensor reports CO2 (carbon dioxide) equivalent
      emission by asset.";
  }
  identity sq-temperature {
    base sensor-quantity;
    description "Sensor reports temperature of asset.";
  }

  // ========== SENSOR-UNIT ==============================
  identity sensor-unit {
    description "Sensor's unit of reporting.";
  }
  identity su-volt {
    base sensor-unit;
    base sq-voltage;
    description "Sensor unit volt, V.";
  }
  identity su-ampere {
    base sensor-unit;
    base sq-current;
    description "Sensor unit ampere, A.";
  }
  identity su-watt {
    base sensor-unit;
    base sq-power;
    description "Sensor unit watt, W.";
  }
  identity su-voltampere {
    base sensor-unit;
    base sq-power;
    description "Sensor unit Volt*Ampere, VA.";
  }
  identity su-kw {
    base sensor-unit;
    base sq-power;
    description "Sensor unit kilowatt, kW.";
  }
  identity su-joule {
    base sensor-unit;
    base sq-energy;
    description "Sensor unit joule, J.";
  }
  identity su-wh {
    base sensor-unit;
    base sq-energy;
    description "Sensor unit watthour, Wh.";
  }
  identity su-kwh {
    base sensor-unit;
    base sq-energy;
    description "Sensor unit kliowatthour, kWh.";
  }
  identity su-kelvin {
    base sensor-unit;
    base sq-temperature;
    description "Sensor unit kelvin, K.";
  }
  identity su-celsius {
    base sensor-unit;
    base sq-temperature;
    description "Sensor unit celsius, C.";
  }
  identity su-farenheit {
    base sensor-unit;
    base sq-temperature;
    description "Sensor unit farenheit, F.";
  }
  identity su-gram {
    base sensor-unit;
    base sq-co2-emission;
    description "Sensor unit gram, g.";
  }
  identity su-kg {
    base sensor-unit;
    base sq-co2-emission;
    description "Sensor unit kliogram, kg.";
  }
  identity su-ton {
    base sensor-unit;
    base sq-co2-emission;
    description "Sensor unit ton, t.";
  }

  // ========== SENSOR-TYPE ==============================
  identity sensor-type {
    description "Sensor's type, i.e. combination of class, quantity and
      unit.";
  }
  identity st-v-in {
    base sensor-type;
    base sc-input;
    base sq-voltage;
    base su-volt;
    description "Sensor reporting Voltage In to asset.";
  }
  identity st-v-out {
    base sensor-type;
    base sc-output;
    base sq-voltage;
    base su-volt;
    description "Sensor reporting Voltage Out of asset.";
  }
  identity st-i-in {
    base sensor-type;
    base sc-input;
    base sq-current;
    base su-ampere;
    description "Sensor reporting Current In to asset.";
  }
  identity st-i-out {
    base sensor-type;
    base sc-output;
    base sq-current;
    base su-ampere;
    description "Sensor reporting Current Out of asset.";
  }
  identity st-p-in-apparent-watt {
    base sensor-type;
    base sc-input;
    base sq-power-apparent;
    base su-voltampere;
    description "Sensor reporting Power In to asset as apparent (I*U)
      power.";
  }
  identity st-p-out-apparent-watt {
    base sensor-type;
    base sc-output;
    base sq-power-apparent;
    base su-voltampere;
    description "Sensor reporting Power Out of asset as apparent (I*U)
      power.";
  }
  identity st-p-in-true-watt {
    base sensor-type;
    base sc-input;
    base sq-power-true;
    base su-watt;
    description "Sensor reporting Power In to asset as true power.";
  }
  identity st-p-out-true-watt {
    base sensor-type;
    base sc-output;
    base sq-power-true;
    base su-watt;
    description "Sensor reporting Power Out of asset as true power.";
  }
  identity st-p-allocated-watt {
    base sensor-type;
    base sc-allocated;
    base sq-power;
    base su-watt;
    description "Sensor reporting Allocated Power for asset.";
  }
  identity st-w-j {
    base sensor-type;
    base sq-energy;
    base su-joule;
    description "Sensor reporting energy draw of asset in J.";
  }
  identity st-w-wh {
    base sensor-type;
    base sq-energy;
    base su-wh;
    description "Sensor reporting energy draw of asset in Wh.";
  }
  identity st-w-kwh {
    base sensor-type;
    base sq-energy;
    base su-kwh;
    description "Sensor reporting energy draw of asset in kWh.";
  }
  identity st-t-k {
    base sensor-type;
    base sq-temperature;
    base su-kelvin;
    description "Sensor reporting Temperature of asset in K.";
  }
  identity st-t-c {
    base sensor-type;
    base sq-temperature;
    base su-celsius;
    description "Sensor reporting Temperature of asset in °C.";
  }
  identity st-t-f {
    base sensor-type;
    base sq-temperature;
    base su-farenheit;
    description "Sensor reporting Temperature of asset in °F.";
  }

  // ========== COLLECTION-METHOD ==============================

  identity collection-method;
  identity cm-polled {
    base collection-method;
  }
  identity cm-gnmi {
    base collection-method;
  }
  identity cm-restconf {
    base collection-method;
  }
  identity cm-netconf {
    base collection-method;
  }
  identity cm-redfish {
    base collection-method;
  }
  identity get-static-url-once {
    base collection-method;
  }
  identity gnmi-polling {
    base cm-gnmi;
    base cm-polled;
  }
  identity restconf-get-polling {
    base cm-restconf;
    base cm-polled;
  }
  identity netconf-get-polling {  
    base cm-netconf;
    base cm-polled;
  }
  identity restconf-yang-push-subscription {
    base cm-restconf;
  }
  identity netconf-yang-push-subscription {
    base cm-netconf;
  }
  identity redfish-polling {
    base cm-redfish;
  }
}
