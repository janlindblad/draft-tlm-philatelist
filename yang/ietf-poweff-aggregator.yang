module ietf-poweff-aggregator {
  yang-version 1.1;
  namespace "urn:ietf:params:xml:ns:yang:ietf-poweff-aggregator";
  prefix ietf-poweff-aggregator;

  import ietf-poweff-types {
    prefix ietf-poweff-types;
  }
  import ietf-poweff-collector {
    prefix ietf-poweff-collector;
  }

  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
     Editor:  Marisol Palmero
              <mailto:mpalmero@cisco.com>";
  description
    "This YANG module defines the POWEFF Aggregator.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions  
  
     Relating to IETF Documents
     (https://trustee.ietf.org/license-info).

     This version of this YANG module is part of RFC XXXX
     (https://www.rfc-editor.org/info/rfcXXXX); see the RFC itself
     for full legal notices.";
  
  revision 2023-10-12 {
    description
      "Initial revision of POWEFF Aggregator";
    reference
      "RFC XXXX: ...";
  }

/*

  An AGGREGATOR ensures data from one or more SOURCE(s) are
  combined into a FLOW using a (sequence of) OPERATIONs (OPs)
  to generate a new data set in the DESTINATION (which could
  be a new collection in the same data storage system as the 
  SOURCE).

                +-------------+
                | AGGREGATOR  |
                +-------------+
                       |
           +-----------+-----------+
           v                       v
      ___________             ___________
     /           \           /           \
    (  SOURCE 1   )         ( DESTINATION )
    |\___________/| FLOW 1  |\___________/|
    |             | ======> |             |
    |             |         |             |
    |             | FLOW 2  |             |
     \___________/  ===##=>  \___________/
                       ||
      ___________      ||
     /           \     ||
    (  SOURCE 2   )   //
    |\___________/| ==
    |             |
    |             |
    |             |
     \___________/


*/

  grouping aggregator-g {
    container poweff-aggregator {
      container sources {
        list source {
          key id;
          leaf id { type ietf-poweff-types:something; }
          uses ietf-poweff-collector:data-endpoint-g;
        }
      }
      container destinations {
        list destination {
          key id;
          leaf id { type ietf-poweff-types:something; }
          uses ietf-poweff-collector:data-endpoint-g;
        }
      }
      container flows {
        list flow {
          key id;
          leaf id { type string; }
          choice chain-position {
            container input {
              leaf source { type leafref { path ../../../../../sources/source/id; }}
            }
            container output {
              leaf destination { type leafref { path ../../../../../destinations/destination/id; }}
            }
            container middle {
              leaf-list inputs { type leafref { path ../../../../flows/flow/id; }}
              leaf pre-process-inputs { type leafref { path ../../../../operations/operation/id; }}
              leaf aggregate { type leafref { path ../../../../operations/operation/id; }}
              leaf post-process-output { type leafref { path ../../../../operations/operation/id; }}
            }
          }
        }
      }
      container operations {
        list operation {
          key id;
          leaf id { type ietf-poweff-types:something; }
          choice op-type {
            container linear-sum {}
            container linear-average {}
            container linear-max {}
            container linear-min {}
            container rolling-average {
              leaf timespan { type ietf-poweff-types:something; }
            }
            container filter-age {
              leaf min-age { type ietf-poweff-types:something; }
              leaf max-age { type ietf-poweff-types:something; }
            }
            container function {
              leaf name { type ietf-poweff-types:something; }
            }
          }
        }
      }
    }
  }
}
