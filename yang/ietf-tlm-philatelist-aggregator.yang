module ietf-tlm-philatelist-aggregator {
  yang-version 1.1;
  namespace 
    "urn:ietf:params:xml:ns:yang:ietf-tlm-philatelist-aggregator";
  prefix ietf-tlm-philatelist-aggregator;

  import ietf-tlm-philatelist-types {
    prefix ietf-tlm-philatelist-types;
  }
  import ietf-tlm-philatelist-index {
    prefix ietf-tlm-philatelist-index;
  }

  organization
    "IETF GREEN (Getting Ready for Energy-Efficient Networking)
     Working Group";
  contact
    "WG Web:   <https://datatracker.ietf.org/group/green/about/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    'This YANG module defines the Telemetry Philatelist Aggregator.
    These definitions are for Philatelist Network Controllers.

    An AGGREGATOR ensures data from one or more SOURCE(s) are
    combined into a FLOW using a (sequence of) OPERATIONs (OPs)
    to generate a new data set in the DESTINATION (which could
    be a new collection in the same data storage system as the 
    SOURCE).

                  +-------------+
                  | AGGREGATOR  |
                  +-------------+
                         |
            +------------+------------+
            v                         v
        ___________               ___________
       /  SOURCE   \             /DESTINATION\
      ( PARTITION 1 )           (  PARTITION  )
      |\___________/| STREAM 1  |\___________/|
      |             | ========> |             |
      |             |           |             |
      |             | STREAM 2  |             |
       \___________/  ===##===>  \___________/
                         ||
        ___________      ||
       /  SOURCE   \     ||
      ( PARTITION 2 )   //
      |\___________/| ==
      |             |
      |             |
      |             |
       \___________/

    '+"
    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.
      
    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";
  
  revision 2024-04-15 {
    description
      "Restructured as part of the Telemetry Philatelist framework";
    reference
      "RFC XXXX: ...";
  }

  container tlm-aggregator {
    description
      "Root container for the Philatelist Aggregator function.
      ";
    container aggregations {
      description 
        "List of aggregation operations that are applied to a set of
        input telemetry streams in a TSDB Partition to form an output 
        stream in a different TSDB Partition.
        ";
      list aggregation {
        key id;
        description 
          "Each aggregation takes one or more input streams from a 
          TSDB Partition, an operation to apply to them, and points
          to an output stream an another TSDB Partition.
          ";
        leaf id {
          type string;
          description
            "The internal id of this aggregation operation.
            ";
        }
        list input {
          key source;
          description 
            "The list of sources/input streams for the aggregation.
            ";
          leaf source { 
            type ietf-tlm-philatelist-index:partition-ref-t; 
            description 
              "The TSDB Partition (bucket, interval, segment, etc.)
              that the input telemetry data is read from.
              "; 
          }
        }
        leaf operation {
          type leafref {
            path ../../../operations/operation/id;
          }
          description 
            "The operation to apply to the input stream(s) in order
            to compute the output stream.
            ";
        }
        container output {
          description 
            "The TSDB Partition to send the computed output to.
            ";
          leaf destination { 
            type ietf-tlm-philatelist-index:partition-ref-t; 
            description 
              "The TSDB Partition (bucket, interval, segment, etc.)
              that the aggregated telemetry data is sent to.
              "; 
          }
        }
      }
    }
    container operations {
      description 
        "The operations that may be applied during the aggregation.
        ";
      list operation {
        key id;
        description 
          "Details about which operation to apply and how.
          ";
        leaf id { 
          type ietf-tlm-philatelist-types:something; 
          description 
            "The internal id of the operation to apply.
            "; 
        }
        choice op-type {
          description 
            "A choice of basic operation types. This set of choices
            may be extended by other modules agumenting the choice.
            ";
          container linear-sum { 
            description 
            "This operation produces the sum of the input streams.

            Since the data points in the input stream are not
            likely to be perfectly aligned in time, this linear-sum
            operation produces a linear interpolation between each 
            point in the time series.
            
            This works well when all inputs are continuously
            receiving additional data points, and when their 
            frequency is roughly the same. A different summing
            operation should be chosen if this is not the case,
            e.g. most-recent-sum.
            "; 
          }
          container linear-average { description "FIXME"; }
          container linear-max { description "FIXME"; }
          container linear-min { description "FIXME"; }
          container rolling-average {
            description "FIXME";
            leaf timespan { 
              type ietf-tlm-philatelist-types:something; 
              description "FIXME"; 
            }
          }
          container filter-age {
            description "FIXME";
            leaf min-age { 
              type ietf-tlm-philatelist-types:something; 
              description "FIXME"; 
            }
            leaf max-age { 
              type ietf-tlm-philatelist-types:something; 
              description "FIXME"; 
            }
          }
          container function {
            description "FIXME";
            leaf name { 
              type ietf-tlm-philatelist-types:something; 
              description "FIXME"; 
            }
          }
        }
      }
    }
  }
}
