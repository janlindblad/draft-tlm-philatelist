module ietf-poweff-provider {
  yang-version 1.1;
  namespace "urn:ietf:params:xml:ns:yang:ietf-poweff-provider";
  prefix ietf-poweff-provider;

  import ietf-poweff-types {
    prefix ietf-poweff-types;
  }

  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
     Editor:  Marisol Palmero
              <mailto:mpalmero@cisco.com>";
  description
    "This YANG module defines the POWEFF Provider.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions  
  
     Relating to IETF Documents
     (https://trustee.ietf.org/license-info).

     This version of this YANG module is part of RFC XXXX
     (https://www.rfc-editor.org/info/rfcXXXX); see the RFC itself
     for full legal notices.";
  
  revision 2023-10-12 {
    description
      "Initial revision of POWEFF Provider";
    reference
      "RFC XXXX: ...";
  }

  grouping provider-g {
    container sensor-catalog {
      config false;
      container sensors {
        list sensor {
          key path;
          leaf path { type ietf-poweff-types:xpath; }
          leaf sensor-type { type identityref { base ietf-poweff-types:sensor-type; }}

          leaf sensor-location {
            type ietf-poweff-types:something;
            description
              "Indicates the current location where the sensor is located
                in the chassis,typically refers to slot";
          }
          leaf sensor-state { // FIXME: What does this mean?
            type ietf-poweff-types:something;
            description
              "Current state of the sensor";
          }
          leaf sensor-current-reading { // FIXME: Do we want a copy of the value here?
            type ietf-poweff-types:something;
            description
              "Current reading of the sensor";
          }
          leaf sensor-precision {
            type string;
            description
              "Maximum deviation to be considered. This attribute mainly
              will apply to drawn power, which corresponds to PSU PowerIn
              measured power or calculated power; assuming discrepancy
              between Real Power, power collected from a power meter, and
              power measured or calculated from the metrics provided by
              the sensors";
          }
          container sensor-thresholds { // FIXME: Is this for generating alarms, or what?
            description 
              "Threshold values for the particular sensor. 
              Default values shall beprovided as part of static data 
              but when configurable need to be pulledfrom the device. 
              Ideally, the sensor should allow configuing 
              thesethreshold values";
        
            leaf minor-low {
              type string; 
              description
                "minor-low";
            }
            leaf minor-high {
              type string; 
              description
                "minor-high";
            }
            leaf major-low {
              type string; 
              description
                "major-low";
            }
            leaf major-high {
              type string; 
              description
                "major-high";
            }
            leaf critical-low {
              type string; 
              description
                "critical-low";
            }
            leaf critical-high {
              type string; 
              description
                "critical-high";
            } 
            leaf shutdown { // FIXME: What does this mean for a sensor?
              type string; 
              description
                "shutdown";
            }                           
          }
        }
      }
    }
  }
}
