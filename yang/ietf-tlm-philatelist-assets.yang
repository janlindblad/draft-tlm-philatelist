module ietf-tlm-philatelist-assets {
  yang-version 1.1;
  namespace 
    "urn:ietf:params:xml:ns:yang:ietf-tlm-philatelist-assets";
  prefix ietf-tlm-philatelist-assets;

  import ietf-lmo {
    prefix ietf-lmo;
  }
  import ietf-lmo-assets {
    prefix ietf-lmo-assets;
  }
  import ietf-tlm-philatelist-index {
    prefix ietf-tlm-philatelist-index;
  }

  organization
    "IETF GREEN (Getting Ready for Energy-Efficient Networking)
     Working Group";
  contact
    "WG Web:   <https://datatracker.ietf.org/group/green/about/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    "This YANG module defines the Telemetry Philatelist linkage to
    DMLMO Assets.
    These definitions are for Philatelist Network Controllers.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.
      
    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";
  
  revision 2024-04-15 {
    description
      "Initial revision.";
    reference
      "RFC XXXX: ...";
  }

  grouping asset-pointer-g {
      description 
        "Pointer to an LMO asset.
        ";
    leaf pertains-to-asset-class {
      type leafref {
        path /ietf-lmo:lmos/ietf-lmo:lmo/ietf-lmo:lmo-class;
      }
      must 
        "derived-from-or-self(current(), 'ietf-lmo-assets:asset')";
      must "../pertains-to-asset-id";
      description 
        "The LMO Asset class of the asset.
        ";
    }
    leaf pertains-to-asset-id {
      type leafref {
        path "/ietf-lmo:lmos/ietf-lmo:lmo"+
          "[ietf-lmo:lmo-class=current()/../pertains-to-asset-class]"
          +"/ietf-lmo:inst/ietf-lmo:id";
      }
      description 
        "The LMO Asset id (within the class) of the asset.
        ";
    }
  }

  augment "/ietf-tlm-philatelist-index:tlm-index"+
          "/ietf-tlm-philatelist-index:partitions"+
          "/ietf-tlm-philatelist-index:partition" {
    description 
      "By augmenting an asset pointer into the TSDB Partition Index,
      controller may clarify which LMO Asset the data in the
      Partition pertains to.
      ";
    uses asset-pointer-g;
  }
}
