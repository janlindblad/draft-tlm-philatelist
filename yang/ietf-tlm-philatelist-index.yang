module ietf-tlm-philatelist-index {
  yang-version 1.1;
  namespace 
    "urn:ietf:params:xml:ns:yang:ietf-tlm-philatelist-index";
  prefix ietf-tlm-philatelist-index;

  import ietf-tlm-philatelist-types {
    prefix ietf-tlm-philatelist-types;
  }

  organization
    "IETF GREEN (Getting Ready for Energy-Efficient Networking)
     Working Group";
  contact
    "WG Web:   <https://datatracker.ietf.org/group/green/about/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    'This YANG module defines the Telemetry Philatelist Index.
    These definitions are for Philatelist Network Controllers.

    A Network Controller with the Collector role programs one or more
    SOURCES (typically Network Elements) to generate a STREAM of 
    telemetry data. The STREAM is sent to a specific DESTINATION
    in a Time Series Database (TSDB).
    
    Each STREAM consists of timestamped sensor values from each
    sensor in a sensor group.

               +-------------+
               |  COLLECTOR  |
               +-------------+                     ___________
                      |                           /DESTINATION\
            +------------------+                 (  PARTITION  )
            v                  v                 |\___________/|
      +------------+    +------------+  STREAM 1 |             |
      |   SOURCE   |    |   SOURCE   |  =======> |             |
      | - sensor 1 |    | - sensor 1 |           |             |
      | - sensor 2 |    | - sensor 4 |  STREAM 2 |             |
      | - sensor 3 |    | - sensor 7 |  =======> |             |
      +------------+    +------------+           |             |
                \\                      STREAM 3 |             |
                  =============================>  \___________/

    '+"
    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.
      
    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";
  
  revision 2024-04-15 {
    description
      "Restructured as part of the Telemetry Philatelist framework";
    reference
      "RFC XXXX: ...";
  }

  typedef partition-ref-t {
    type leafref { 
      path 
        "/ietf-tlm-philatelist-index:tlm-index"+
        "/ietf-tlm-philatelist-index:partitions"+
        "/ietf-tlm-philatelist-index:partition"+
        "/ietf-tlm-philatelist-index:id"; 
    }
    description 
      "Pointer to a specific TSDB partition 
      (aka. bucket, interval, segment, etc.)
      ";
  }
  grouping tsdb-partition-g {
    description 
      "Grouping for identifying and connecting to a specific TSDB
      partition (aka. bucket, interval, segment, etc.)
      ";
    leaf url { 
      type ietf-tlm-philatelist-types:something; 
      description 
        "The URL to use to connect to the TSDB.
        "; 
    }
    leaf organization { 
      type ietf-tlm-philatelist-types:something; 
      description 
        "The organization this partition belongs to.
        Leaving this unset means the 'default' organization.
        "; 
    }
    leaf partition {
      type ietf-tlm-philatelist-types:something; 
      description 
        "The TSDB partition (aka. bucket, interval, segment, etc.)
        that the collected data is stored in.
        "; 
    }
    container impl-specific {
      description 
        "Implementation specific key-valye pairs for establising and
        maintaining the collection connections.
        ";
      list binding {
        key key;
        description
          "List of key-value bindings. The meaning of these key-value
          pairs is implementation dependent.
          ";
        leaf key { 
          type string; 
          description 
            "The key part of the key-value pair.
            The set of key values that are defined is implementation
            dependent.
            "; 
        }
        choice value-type {
          description 
            "The value part of the key-value pair. The value part may
            have several different formats, and implementations may
            augment yet other formats into this choice.
            ";
          leaf value { 
            type string; 
            description 
              "The value part of the key-value pair as a simple
              string value.
              "; 
          }
          leaf-list values { 
            type string; 
            ordered-by user; 
            description 
              "The value part of the key-value pair as a collection
              of string values.
              "; 
          }
          leaf env-var { 
            type string; 
            description 
              "The value part of the key-value pair. The actual
              value is provided by an operating system environment
              variable. The name of that environment variable is
              given by this leaf. Case sensitive.

              The set of environment variable names that are defined
              is implementation dependent.
              "; 
          }
        }
      }
    }
  }

  container tlm-index {
    description 
      "List of TSDB Partitions referenced by this Network Controller.
      ";
    container partitions {
      description 
        "Container for all the TSDB Partition access information.
        ";
      list partition {
        key id;
        description 
          "TSDB Partition access information for the Partitions that
          this Network Controller is aware of.
          ";
        leaf id { 
          type ietf-tlm-philatelist-types:something; 
          description 
            "The Network Controller's internal identifier for this
            TSDB Partition.
            "; 
        }
        uses tsdb-partition-g;
      }
    }
  }
}
